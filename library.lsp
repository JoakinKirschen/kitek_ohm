(defun c:switches()
(Blk_Lib "ElekBlocks" (strcat BlockLibBase$ "\\Blocks\\ElekSymb\\ElekBlocks.def") nil)
)
(defun c:sockets()
(Blk_Lib "ElekBlocks" (strcat BlockLibBase$ "\\Blocks\\ElekSymb\\ElekBlocks.def") nil)
)
(defun c:sockets()
(Blk_Lib "ElekBlocks" (strcat BlockLibBase$ "\\Blocks\\ElekSymb\\ElekBlocks.def") nil)
)
