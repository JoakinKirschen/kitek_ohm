(DEFUN c:UPDATE12 ()
	(COMMAND "._STYLE" "standard" "iso8" "" "1.00" "0.00" "n" "n" "n")
	(SETQ NAM (ENTNEXT))
	(WHILE (/= NAM NIL)
		(PRINC ".")
		(SETQ INF (ENTGET NAM))
		(IF (= (CDR (ASSOC 0 iNF)) "ATTDEF")
			(PROGN
				(SETQ INF (SUBST (CONS 41 1.00) (ASSOC 41 INF) INF))
				(ENTMOD INF)
			)
		)
		(SETQ NAM (ENTNEXT NAM))
	)
	(COMMAND "._REGEN")
	(PRINC)
)

(LOAD "PUTCLPS")
