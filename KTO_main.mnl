;[                                                           ]
					;[            KTO_main.mnl                                   ]
					;[                                                           ]
					;[        KiTek Ohm voor acad                                ]
					;[                                                           ]
					;[by Joakin Kirschen special thanks to LeeMac and TerryCAD   ]

(vl-load-com)
;;Initialise Functions
(if (not KTO_main)
  (load "KTO_main.lsp")
)
(if (not KTO_support)
  (load "KTO_support.lsp")
)

(if (not KTO_frstring)
  (load "KTO_frstring.lsp")
)

(if (not KTO_multiline)
  (load "KTO_multiline.lsp")
)

(if (not KTO_loadlinetypes)
  (load "KTO_loadlinetypes.lsp")
)

(if (not KTO_lib)
  (load "KTO_lib.lsp")
)



(if (not KTO_lib)
  (load "KTO_lib.lsp")
)

(if (not KTO_libtrigger)
  (load "KTO_libtrigger.lsp")
)

;;-----[ Globale variabelen ]-------------
(setq KTO_version 0.01)
(setq KTO_stamp 8140)
(setq KTO_path (vl-filename-directory (findfile "KTO_main.mnl")))
(if (not(getenv "KTO_Disipline"))(setenv "KTO_Disipline" "TI-"))			;register presets
(if (not(getenv "KTO_UpdateSettings"))(setenv "KTO_UpdateSettings" "2"))	;register presets
;(if (not(getenv "KTO_AutosaveSettings"))(setenv "KTO_AutosaveSettings" "50"))
;(setq gl_autosave (atoi (getenv "KTO_AutosaveSettings")))

;;-----[ Preset KiTek Ohm ]-----------------------------
(princ "\n\nPreset KiTek Ohm...\n")
;(menucmd "p30=+Lab2012.POPL1")
;(menucmd "p30=+Lab2012.POPL2")
;(menucmd "p30=+Lab2012.POPL3")
;(menucmd "p30=+Lab2012.POP1")
;(setq ccCurColor "1")
;(setq ccCurLType "CONTINUOUS")
;(setq arctoggle "0")
(setvar "PEDITACCEPT" 1)
(setvar "layernotify" 0)
(setvar "cmdecho" 0)
(setvar "annoautoscale" 0)
(if (> (atof (getvar 'AcadVer))  18.2) (setvar "startmode" 0))
(setvar "annoallvisible" 1)
(setvar "hpcolor" "bylayer")
(setvar "qaflags" 0)
(setenv "TemplatePath" "C:\\Users\\P701650\\AppData\\Roaming\\AutoCAD 2016\\kitek_ohm\\KTO_template")
(KTO_Statusb)
;(KTO_moveparmeters)
;(KTO_moveparmeters)
(setvar "cmdecho" 1)
(princ "\n Done!\n")
